module omg-extensions {
  namespace "urn:yang:omg:extensions";
  prefix e;

  extension require-admin {
    description
      "Extend an rpc or node to require admin permissions.";
  }

  extension human-name {
    description
      "Extend a node to provide a human readable name.";
    argument name;
  }

  extension type-desc {
    description
      "Extend a type to add a desc.";
    argument name;
  }

  extension parse-validation {
    description
      "Example of parse-validation extension which should be put only under leaf nodes.";
  }

  extension compile-validation {
    description
      "Example of compile-validation extension which should be put only under leaf nodes.";
  }
}
