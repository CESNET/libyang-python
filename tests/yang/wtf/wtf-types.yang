module wtf-types {
  namespace "urn:yang:wtf:types";
  prefix t;

  import omg-extensions { prefix ext; }

  typedef str {
    type string;
  }

  typedef host {
    type str {
      pattern "[a-z]+";
    }
  }

  extension signed;
  extension unsigned;

  typedef unsigned {
    type union {
      type uint16 {
        t:unsigned;
        ext:type-desc "<uint16>";
      }
      type uint32 {
        ext:type-desc "<uint32>";
        t:unsigned;
      }
    }
  }

  typedef signed {
    type union {
      type int16 {
        ext:type-desc "<int16>";
        t:signed;
      }
      type int32 {
        ext:type-desc "<int32>";
        t:signed;
      }
    }
  }

  typedef number {
    type union {
      type unsigned;
      type signed;
    }
  }

  typedef protocol {
    type enumeration {
      enum http;
      enum https;
      enum ftp {
        status deprecated;
      }
      enum sftp;
    }
  }

  typedef permissions {
    type bits {
      bit read;
      bit write;
      bit execute;
    }
  }
}
