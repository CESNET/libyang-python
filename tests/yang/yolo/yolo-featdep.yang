module yolo-featdep {
  yang-version 1.1;
  namespace "urn:yang:yolo:featdep";
  prefix featdep;

  revision 2026-09-23 {
    description
      "Initial version.";
  }

  feature remote-feature {
    description
      "Defined here so yolo-featuser can reference it by prefix.";
  }
}
