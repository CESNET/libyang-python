module yolo-featuser {
  yang-version 1.1;
  namespace "urn:yang:yolo:featuser";
  prefix featuser;

  import yolo-featdep { prefix dep; }

  revision 2026-09-23 {
    description
      "Initial version.";
  }

  feature local-feature {
    description
      "Unused by `gated` - only here so this module has a non-empty
       feature list of its own.";
  }

  leaf gated {
    type string;
    if-feature "dep:remote-feature";
    description
      "Gated by another module's feature, referenced by prefix.";
  }
}
